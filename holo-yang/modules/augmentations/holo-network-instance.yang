module holo-network-instance {
  yang-version 1.1;
  namespace "http://holo-routing.org/yang/holo-network-instance";
  prefix holo-ni;

  import ietf-routing {
    prefix rt;
  }

  import ietf-network-instance {
    prefix ni;
  }

  organization
    "Holo Routing Stack";

  description
    "This module binds routing protocol instances to network
     instances (VRFs).

     Rather than mounting per-network-instance schema (RFC 8529
     schema-mount), Holo keeps control-plane protocols under the
     top-level /routing tree and associates each instance with a
     network instance by name. This preserves the flat schema while
     supporting VRF-scoped routing.";

  augment "/rt:routing/rt:control-plane-protocols/rt:control-plane-protocol" {
    description
      "Associates a control-plane protocol instance with a network
       instance (VRF). When unset, the instance runs in the default
       network instance.";
    leaf network-instance {
      type leafref {
        path "/ni:network-instances/ni:network-instance/ni:name";
      }
      description
        "Name of the network instance (VRF) this protocol instance
         runs in.";
    }
  }

  augment "/ni:network-instances/ni:network-instance" {
    description
      "Operational state learned for the network instance (VRF).";
    container state {
      config false;
      description "Network-instance operational state.";
      leaf table-id {
        type uint32;
        description
          "Kernel routing table id, learned from the VRF device of the
           same name. Absent until the VRF device is present.";
      }
    }
  }
}
